module sample-module {
  // namespace
  namespace "urn:ietf:params:xml:ns:yang:sample-module";

  prefix sm;

  import ietf-module-tags {
     prefix mtags;
  }

  // meta
  organization "IETF NetMod Working Group (NetMod)";

  contact
    "NetMod Working Group - <netmod@ietf.org>";

  description

    "This is a sample module to demonstrate the proper way to
     include searchable classfication tags in a module.";

  revision "2017-10-22" {
    description
      "Initial revision.";
    reference "RFC TBD";
  }

  container module-tags {
    description
      "A list of classification tags associated with this
       module. The following predefined tags MUST
       be included by an implementation:
	 - ietf:foo1
	 - ietf:bar1
       The following predefined tags SHOULD be included by an
       implementation:
	 - ietf:foo2
	 - ietf:bar2
      ";
    uses mtags:module-tags;
  }
  
  container real-stuff {
    description
      "This is the start of the module being defined";
  }
}
